UC-Server-Access-Protocol-ClientPersistence
	{ iso(1) identified-organization(3) dod(6) internet(1) private(4) enterprise(1) estos(10924) uc-server-access-protocol-v2(2) clientpersistence(23) }

-- @category ClientPersistence
-- @brief Client persistence interface
-- @long
-- ## Module description
-- This module defines structures and operations for a CRUD item store and its eventing.
-- With these operations, each client can persist client specific data on the UCServer and can attach to the according change notify interface.

DEFINITIONS
IMPLICIT TAGS ::=
BEGIN

IMPORTS
AsnRequestError, UTF8StringList FROM UC-Server-Access-Protocol-Common
;

-- @brief ResultDetails 
-- @long
-- The server always responds asynchronously with a corresponding iResult in the event - in case of an error, the server uses a corresponding ErrorCode from this list here.
AsnClientPersistenceResultDetailsEnum ::= ENUMERATED
{
	noerror(0),						-- No error
	itemstoreaccessdenied(1),		-- Access to ItemStore not allowed
	dataaccessdenied(2),			-- Access denied (read/write)
	invalidsubscription(3),			-- Invalid Subscribe/Unsubscribe
	invalidcrossrefid(4),			-- Invalid CrossRef ID given
	invalidkey(5),					-- Invalid key element
	invaliddata(6),					-- Invalid data element (e.g. too big)
	clientpersistenceoverload(7),	-- Too many requests (a client should only have 10 requests in parallel on the UCServer)
	databasefail(8),				-- Database error (read/write)
	revisionoutdated(9),			-- Client requests with a revision that is too old, i.e. client must discard its data and request again (= get initial data)
	clientpersistencedisabled(99)	-- ClientPersistence system is not active on the UCServer
}



-- @brief Definition of persistence items
-- @long
-- An ItemStore can hold any persistence items. A persistence item always belongs to exactly one ItemStore.
-- The key of a persistence item (u8sItemStoreID) must be unique within the ItemStore.
-- If the client does not specify a u8sItemStoreID when creating an item, the server generates this key itself.
-- The client itself is responsible for managing the payload in an appropriate way.
AsnClientPersistenceItem ::= SEQUENCE
{
	u8sItemStore    	UTF8String,         -- Item store name, e.g. "FAQEntry", "usersettings"
	u8sItemStoreID	  	UTF8String,			-- Key of an item, it must be unique in an item store
	data    	       	UTF8String,         -- Value data of the item
	iRevision   	[0] INTEGER OPTIONAL,	-- Revision of the item
	...
}

AsnClientPersistenceItemList ::= SEQUENCE OF AsnClientPersistenceItem


-- @brief Adding a new item
-- @long
-- A new item is added to the ItemStore. 
-- The client must be subscribed to this ItemStore and pass a unique (for the client session) u8sCrossRefID.
-- If the client does not provide a StoreID, the server generates a key itself.
-- Confirmation from the server is via the asnClientPersistenceEvent event with the corresponding u8sCrossRefID.
-- The configured access permissions are taken into account and acknowledged with an error if necessary.
asnClientPersistenceCreate OPERATION
	ARGUMENT	arg AsnClientPersistenceCreateArgument
	RESULT		res AsnClientPersistenceCreateResult
	ERRORS		{AsnRequestError} 
::= 4301

-- @brief Argument for asnClientPersistenceCreate
--  
AsnClientPersistenceCreateArgument ::= SEQUENCE
{
	u8sCrossRefID		UTF8String, -- Must be unique in a client session and will be generated by the client
	u8sItemStore 		UTF8String, -- ItemStore of the item
	u8sItemStoreID   [0] UTF8String OPTIONAL, -- when given, the u8sItemStoreID must not exist in the item store already
	data    	       UTF8String,            -- Data of the item
	...
}

-- @brief Result of asnClientPersistenceCreate
--  
AsnClientPersistenceCreateResult ::= SEQUENCE
{
	...
}


-- @brief Abruf von Elementen eines ItemStore
-- @long
-- The client retrieves one or more items from the passed ItemStore. 
-- The client must be subscribed to this ItemStore and pass a unique (for the client session) u8sCrossRefID.
-- If the client does not provide a StoreID, all available items in the ItemStore will be returned.
-- The server's response is via the asnClientPersistenceEvent event with the corresponding u8sCrossRefID.
-- The configured access permissions are taken into account and acknowledged with an error if necessary.
asnClientPersistenceRead OPERATION
	ARGUMENT	arg AsnClientPersistenceReadArgument
	RESULT		res AsnClientPersistenceReadResult
	ERRORS		{AsnRequestError} 
::= 4302


-- @brief Enumeration for iItemKeyWildcardType in AsnClientPersistenceReadArgument
AsnClientPersistenceReadWildcardTypeEnum ::= ENUMERATED
{
    -- no wildcard read - key has to match exactly (DEFAULT)
	noWildcard(0),
	
	-- the given key is used as prefix for result key(s)
	-- example: given key "apple" will receive elements like "apple" "applesauce" "applejack" but not "pineapple"
	prefixKey(1),
	
	-- the given key is used as postfix for result key(s)
	-- example: given key "apple" will receive elements like "apple" "pineappleapple" "crabapple" but not "applesauce"
	postfixKey(2)	
}

-- @brief Argument for asnClientPersistenceRead
--
AsnClientPersistenceReadArgument ::= SEQUENCE
{
	-- The CrossRef ID is generated by the client and must be unique within the ClientSession.
	u8sCrossRefID				UTF8String, 
	
	-- The ItemStore to read the items from.
	u8sItemStore 				UTF8String, 
	
	-- Key of the item to read (without specification all available items are returned).
	u8sItemStoreID 				[0] UTF8String OPTIONAL, 
	
	-- Without specifying a u8sItemStoreID all items with larger revision will be returned.
	-- (i.e. the parameter is only evaluated if *no* u8sItemStoreID was specified)
	iLastKnownGlobalRevision 	[1] INTEGER OPTIONAL, 
	
	-- Key of the item (u8sItemStoreID) is to be treated as wildcard prefix/postfix
	-- i.e. all items starting with the u8sItemStoreID prefix/postfix will be returned.<br />
	-- See AsnClientPersistenceReadWildcardTypeEnum for possible values.
	iItemKeyWildcardType		[2]	INTEGER OPTIONAL,	 

	-- False: default/standard behavior - all matching items are returned.
	-- True: only the number of currently available/accessible items is returned (in the optional iChangedItemsCount parameter) - but not their contents
	-- (works only if iItemKeyWildcardType is prefixKey or postfixKey).
	bCountAvailableItemsOnly	[3] BOOLEAN OPTIONAL, 	

	-- Limit the number of (wildcard) items returned.
	-- (works only if iItemKeyWildcardType is prefixKey or postfixKey)
	iItemLimit					[4] INTEGER OPTIONAL,
	
	...
}

-- @brief Result of asnClientPersistenceRead
-- 
AsnClientPersistenceReadResult ::= SEQUENCE
{
	...
}


-- @brief Updating an existing element
-- @long
-- The client wants to update an existing item in the passed ItemStore.<br />
-- The client must be subscribed to this ItemStore and pass a unique (for the client session) u8sCrossRefID.
-- If the client does not provide a StoreID, all available items in the ItemStore will be returned.
-- The server's response is via the asnClientPersistenceEvent event with the corresponding u8sCrossRefID.
-- The configured access permissions are taken into account and acknowledged with an error if necessary. 
asnClientPersistenceUpdate OPERATION
	ARGUMENT	arg AsnClientPersistenceUpdateArgument
	RESULT		res AsnClientPersistenceUpdateResult
	ERRORS		{AsnRequestError} 
::= 4303

-- @brief Argument for asnClientPersistenceUpdate
--
AsnClientPersistenceUpdateArgument ::= SEQUENCE
{
	u8sCrossRefID		UTF8String, -- Must be unique in a client session and will be generated by the client.
	u8sItemStore 		UTF8String, -- ItemStore of the item.
	u8sItemStoreID 	 	UTF8String, -- Key of the item.
	data    	    	UTF8String, -- Data of the item.
	...
}

-- @brief Result of asnClientPersistenceUpdate
--
AsnClientPersistenceUpdateResult ::= SEQUENCE
{
	...
}


-- @brief Delete an existing item.
-- @long
-- The client wants to delete an existing item in the passed ItemStore.<br />
-- The client must be subscribed to this ItemStore and pass a unique (for the client session) u8sCrossRefID.
-- If the client does not provide a StoreID, all available items in the ItemStore will be returned.
-- The server's response is via the asnClientPersistenceEvent event with the corresponding u8sCrossRefID.
-- The configured access permissions are taken into account and acknowledged with an error if necessary.
asnClientPersistenceDelete OPERATION
	ARGUMENT	arg AsnClientPersistenceDeleteArgument
	RESULT		res AsnClientPersistenceDeleteResult
	ERRORS		{AsnRequestError} 
::= 4304


-- @brief Argument for asnClientPersistenceDelete
--
AsnClientPersistenceDeleteArgument ::= SEQUENCE
{
	u8sCrossRefID		UTF8String, -- Must be unique in a client session and will be generated by the client.
	u8sItemStore 	   	UTF8String, -- ItemStore of the item.
	u8sItemStoreID  	UTF8String, -- Key of the item.
	...
}

-- @brief Result of asnClientPersistenceDelete
AsnClientPersistenceDeleteResult ::= SEQUENCE
{
	...
}


-- @brief Subscribe for changes in the item store.
-- @long
-- The client registers for event on changes of items within the passed ItemStore.<br />
-- Subscribe can be called multiple times and is additive in this case.
-- The client must pass a unique (for the client session) u8sCrossRefID.
-- The server's response is via the asnClientPersistenceEvent event with the corresponding u8sCrossRefID.
-- The configured access permissions are taken into account and acknowledged with an error if necessary.
asnClientPersistenceSubscribe OPERATION
	ARGUMENT	arg AsnClientPersistenceSubscribeArgument
	RESULT		res AsnClientPersistenceSubscribeResult
	ERRORS		{AsnRequestError} 
::= 4305


-- @brief Enumeration for iSubscribeType of AsnClientPersistenceSubscribeArgument
AsnClientPersistenceSubscribeTypeEnum ::= ENUMERATED
{
	subscribe(1),
	unsubscribe(2)
}

-- @brief Argument for asnClientPersistenceSubscribe
--
AsnClientPersistenceSubscribeArgument ::= SEQUENCE
{
	u8sCrossRefID				UTF8String,  -- Must be unique in a client session and will be generated by the client.
	iSubscribeType 				INTEGER,	 -- Subscribe or Unsubscribe, see AsnClientPersistenceSubscribeTypeEnum.
	u8sItemStore				UTF8String,  -- ItemStore for which the action is to be performed.
	...
}

-- @brief Result of asnClientPersistenceSubscribe
--
AsnClientPersistenceSubscribeResult ::= SEQUENCE
{
	...
}


-- @brief Event from the UCServer for signalling changes in an item store.
-- @long
-- The server responds via the asnClientPersistenceEvent with the corresponding u8sCrossRefID.<br />
-- The configured access permissions are taken into account and acknowledged with an error if necessary. 
-- The server event is also delivered if the unique ID of the server database has changed.
-- The client should then discard its (locally cached) data and request new initial data from the server.
asnClientPersistenceEvent OPERATION
	ARGUMENT	arg AsnClientPersistenceEventArgument
::= 4306


-- @brief Argument for asnClientPersistenceEvent
--
AsnClientPersistenceEventArgument ::= SEQUENCE
{
	iResult  				INTEGER, -- See AsnClientPersistenceResultDetailsEnum for possible values.
	u8sCrossRefID			UTF8String, -- If it is not empty, it is a response to a request from the client, otherwise it is a UCServer generated event.
	iGlobalRevision 		[0] INTEGER OPTIONAL, -- The transaction ID managed by the server that led to this event.
	changedItems   			[1] AsnClientPersistenceItemList OPTIONAL, -- List of changed items (the list may contain items from several ItemStores)
	deletedItems   			[2] AsnClientPersistenceItemList OPTIONAL, -- List of deleted items (the list may contain items from several ItemStores)
	u8sDatabaseID			[3] UTF8String OPTIONAL, -- Unique ID of the current server database, sent by the server on request - or automatically if the DB ID has changed.
	iAvailableItemsCount 	[4] INTEGER OPTIONAL, -- Is only returned if only the number of elements was requested for asnClientPersistenceRead.
	...
}


-- @brief Abfrage der Datenbank ID
-- @long
-- Returns a unique ID of the database, which clients can use to determine whether the server is using a new database.<br />
-- This may be the case, for example, if the server database has been deleted.
-- This method is the only synchronous method of the client persistence interface.
asnClientPersistenceGetDatabaseID OPERATION
	ARGUMENT	arg AsnClientPersistenceGetDatabaseIDArgument
	RESULT		res AsnClientPersistenceGetDatabaseIDResult
	ERRORS		{AsnRequestError}
::= 4307

-- @brief Argument for asnClientPersistenceGetDatabaseID
--
AsnClientPersistenceGetDatabaseIDArgument ::= SEQUENCE
{
	...
}

-- @brief Result of asnClientPersistenceGetDatabaseID
--
AsnClientPersistenceGetDatabaseIDResult ::= SEQUENCE
{
	u8sDatabaseID		UTF8String, -- Unique ID der aktuellen Server Datenbank
	...
}


END
